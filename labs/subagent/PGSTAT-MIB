PGSTAT-MIB DEFINITIONS ::= BEGIN

IMPORTS
	MODULE-IDENTITY, OBJECT-TYPE, NOTIFICATION-TYPE,
	Counter32, Gauge32, Integer32, enterprises
		FROM SNMPv2-SMI
	Float
		FROM UCD-SNMP-MIB
	DisplayString, DateAndTime, TruthValue
		FROM SNMPv2-TC;

pgsql MODULE-IDENTITY
	LAST-UPDATED "201109062145Z"	-- 06 September 2011
	ORGANIZATION "pgstatmib Development Team"
	CONTACT-INFO
		"E-mail: pgstatmib-devel@pgfoundry.org
		WWW: http://pgstatmib.projects.postgresql.org"
	DESCRIPTION
		"MIB to describe PostgreSQL statistics"

	::= { enterprises 27645 }

pgStatMIB 	OBJECT IDENTIFIER ::= { pgsql 3 }

----------------------------------------------------------------

pgstatDatabaseTable OBJECT-TYPE
    SYNTAX     SEQUENCE OF PgStatDatabaseEntry
    MAX-ACCESS not-accessible
    STATUS     current
    DESCRIPTION
        "TODO: The (conceptual) table of devices contained by the host."
    ::= { pgStatMIB 1 }

pgstatDatabaseEntry OBJECT-TYPE
    SYNTAX     PgStatDatabaseEntry
    MAX-ACCESS not-accessible
    STATUS     current
    DESCRIPTION
        "TODO: A (conceptual) entry for one device contained by the
        host.  As an example, an instance of the hrDeviceType
        object might be named hrDeviceType.3"
    INDEX { pgstatDatabaseIndex }
    ::= { pgstatDatabaseTable 1 }

PgStatDatabaseEntry ::= SEQUENCE {
	pgstatDatabaseIndex		Integer32,
	pgstatDatabaseName		DisplayString,
	pgstatDatabaseBackends		Gauge32,
	pgstatDatabaseCommits		Counter32,
	pgstatDatabaseRollbacks		Counter32,
	pgstatDatabaseBlocksRead	Counter32,
	pgstatDatabaseBlocksHit		Counter32,
	pgstatDatabaseTuplesReturned	Counter32,
	pgstatDatabaseTuplesFetched	Counter32,
	pgstatDatabaseTuplesInserted	Counter32,
	pgstatDatabaseTuplesUpdated	Counter32,
	pgstatDatabaseTuplesDeleted	Counter32,
	pgstatDatabaseRollbackRatio	Float,
	pgstatDatabaseCacheHitRatio	Float,
	pgstatDatabaseTuplesModified	Counter32
    }

pgstatDatabaseIndex OBJECT-TYPE
    SYNTAX     Integer32 (1..2147483647)
    MAX-ACCESS read-only
    STATUS     current
    DESCRIPTION
        "TODO: A unique value for each device contained by the host.
        The value for each device must remain constant at
        least from one re-initialization of the agent to the
        next re-initialization."
    ::= { pgstatDatabaseEntry 1 }

pgstatDatabaseName OBJECT-TYPE
    SYNTAX     DisplayString (SIZE (0..64))
    MAX-ACCESS read-only
    STATUS     current
    DESCRIPTION
        "TODO: An indication of the type of device."
    ::= { pgstatDatabaseEntry 2 }

pgstatDatabaseBackends OBJECT-TYPE
    SYNTAX     Gauge32
    MAX-ACCESS read-only
    STATUS     current
    DESCRIPTION
        "TODO: A textual description of this device, including the
        device's manufacturer and revision, and optionally,
        its serial number."
    ::= { pgstatDatabaseEntry 3 }

pgstatDatabaseCommits OBJECT-TYPE
    SYNTAX     Counter32
    MAX-ACCESS read-only
    STATUS     current
    DESCRIPTION
        "TODO: The product ID for this device."
    ::= { pgstatDatabaseEntry 4 }

pgstatDatabaseRollbacks OBJECT-TYPE
    SYNTAX     Counter32
    MAX-ACCESS read-only
    STATUS     current
    DESCRIPTION
        "TODO: The current operational state of the device described
        by this row of the table."
    ::= { pgstatDatabaseEntry 5 }

pgstatDatabaseBlocksRead OBJECT-TYPE
    SYNTAX     Counter32
    MAX-ACCESS read-only
    STATUS     current
    DESCRIPTION
        "TODO: The number of errors detected on this device.  It
        should be noted that as this object has a SYNTAX of
        Counter32, that it does not have a defined initial
        value.  However, it is recommended that this object be
        initialized to zero, even though management stations
        must not depend on such an initialization."
    ::= { pgstatDatabaseEntry 6 }

pgstatDatabaseBlocksHit OBJECT-TYPE
    SYNTAX     Counter32
    MAX-ACCESS read-only
    STATUS     current
    DESCRIPTION
        "TODO: The number of errors detected on this device.  It
        should be noted that as this object has a SYNTAX of
        Counter32, that it does not have a defined initial
        value.  However, it is recommended that this object be
        initialized to zero, even though management stations
        must not depend on such an initialization."
    ::= { pgstatDatabaseEntry 7 }

pgstatDatabaseTuplesReturned OBJECT-TYPE
    SYNTAX     Counter32
    MAX-ACCESS read-only
    STATUS     current
    DESCRIPTION
        "TODO: The number of errors detected on this device.  It
        should be noted that as this object has a SYNTAX of
        Counter32, that it does not have a defined initial
        value.  However, it is recommended that this object be
        initialized to zero, even though management stations
        must not depend on such an initialization."
    ::= { pgstatDatabaseEntry 8 }

pgstatDatabaseTuplesFetched OBJECT-TYPE
    SYNTAX     Counter32
    MAX-ACCESS read-only
    STATUS     current
    DESCRIPTION
        "TODO: The number of errors detected on this device.  It
        should be noted that as this object has a SYNTAX of
        Counter32, that it does not have a defined initial
        value.  However, it is recommended that this object be
        initialized to zero, even though management stations
        must not depend on such an initialization."
    ::= { pgstatDatabaseEntry 9 }

pgstatDatabaseTuplesInserted OBJECT-TYPE
    SYNTAX     Counter32
    MAX-ACCESS read-only
    STATUS     current
    DESCRIPTION
        "TODO: The number of errors detected on this device.  It
        should be noted that as this object has a SYNTAX of
        Counter32, that it does not have a defined initial
        value.  However, it is recommended that this object be
        initialized to zero, even though management stations
        must not depend on such an initialization."
    ::= { pgstatDatabaseEntry 10 }

pgstatDatabaseTuplesUpdated OBJECT-TYPE
    SYNTAX     Counter32
    MAX-ACCESS read-only
    STATUS     current
    DESCRIPTION
        "TODO: The number of errors detected on this device.  It
        should be noted that as this object has a SYNTAX of
        Counter32, that it does not have a defined initial
        value.  However, it is recommended that this object be
        initialized to zero, even though management stations
        must not depend on such an initialization."
    ::= { pgstatDatabaseEntry 11 }

pgstatDatabaseTuplesDeleted OBJECT-TYPE
    SYNTAX     Counter32
    MAX-ACCESS read-only
    STATUS     current
    DESCRIPTION
        "TODO: The number of errors detected on this device.  It
        should be noted that as this object has a SYNTAX of
        Counter32, that it does not have a defined initial
        value.  However, it is recommended that this object be
        initialized to zero, even though management stations
        must not depend on such an initialization."
    ::= { pgstatDatabaseEntry 12 }

pgstatDatabaseRollbackRatio OBJECT-TYPE
    SYNTAX     Float
    MAX-ACCESS read-only
    STATUS     current
    DESCRIPTION
        "TODO: ..."
    ::= { pgstatDatabaseEntry 21 }

pgstatDatabaseCacheHitRatio OBJECT-TYPE
    SYNTAX     Float
    MAX-ACCESS read-only
    STATUS     current
    DESCRIPTION
        "TODO: ..."
    ::= { pgstatDatabaseEntry 22 }

pgstatDatabaseTuplesModified OBJECT-TYPE
    SYNTAX     Counter32
    MAX-ACCESS read-only
    STATUS     current
    DESCRIPTION
        "TODO: ..."
    ::= { pgstatDatabaseEntry 23 }

----------------------------------------------------------------

pgstatBgWriter	OBJECT IDENTIFIER ::= { pgStatMIB 10 }

pgstatBgWriterCheckpointsTimed OBJECT-TYPE
	SYNTAX		INTEGER
	MAX-ACCESS	read-only
	STATUS		current
	DESCRIPTION
		"checkpoints_timed: number of scheduled checkpoints"
	::= { pgstatBgWriter 1 }

pgstatBgWriterCheckpointsRequested OBJECT-TYPE
	SYNTAX		INTEGER
	MAX-ACCESS	read-only
	STATUS		current
	DESCRIPTION
		"checkpoints_req: number of requested checkpoints"
	::= { pgstatBgWriter 2 }

pgstatBgWriterBuffersCheckpoint OBJECT-TYPE
	SYNTAX		INTEGER
	MAX-ACCESS	read-only
	STATUS		current
	DESCRIPTION
		"buffers_checkpoint: buffers written by checkpoints"
	::= { pgstatBgWriter 3 }

pgstatBgWriterBuffersClean OBJECT-TYPE
	SYNTAX		INTEGER
	MAX-ACCESS	read-only
	STATUS		current
	DESCRIPTION
		"buffers_clean: buffers written by cleaning scans"
	::= { pgstatBgWriter 4 }

pgstatBgWriterMaxWrittenClean OBJECT-TYPE
	SYNTAX		INTEGER
	MAX-ACCESS	read-only
	STATUS		current
	DESCRIPTION
		"maxwritten_clean: the number of times the background writer stopped a cleaning scan because it had written too many buffers"
	::= { pgstatBgWriter 5 }

pgstatBgWriterBuffersBackend OBJECT-TYPE
	SYNTAX		INTEGER
	MAX-ACCESS	read-only
	STATUS		current
	DESCRIPTION
		"buffers_backend: buffers written by backends (that is, not by the background writer)"
	::= { pgstatBgWriter 6 }

pgstatBgWriterBuffersAllocated OBJECT-TYPE
	SYNTAX		INTEGER
	MAX-ACCESS	read-only
	STATUS		current
	DESCRIPTION
		"buffers_alloc: total buffers allocated"
	::= { pgstatBgWriter 7 }

---------------------------------------

END
