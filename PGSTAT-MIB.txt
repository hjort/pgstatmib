PGSTAT-MIB DEFINITIONS ::= BEGIN

IMPORTS
	MODULE-IDENTITY, OBJECT-TYPE, NOTIFICATION-TYPE,
	Counter32, Gauge32, Integer32, Unsigned32, enterprises
		FROM SNMPv2-SMI
	Float
		FROM UCD-SNMP-MIB
	DisplayString, DateAndTime, TruthValue
		FROM SNMPv2-TC;

pgsql MODULE-IDENTITY
	LAST-UPDATED "201601262134Z"	-- 26 January 2016
	ORGANIZATION "pgStatMIB Development Team"
	CONTACT-INFO
		"E-mail: pgstatmib@hjort.co
		WWW: http://github.com/hjort/pgstatmib"
	DESCRIPTION
		"MIB to describe PostgreSQL statistics aiming at monitoring database activity"

	::= { enterprises 27645 }

pgStatMIB 	OBJECT IDENTIFIER ::= { pgsql 3 }

----------------------------------------------------------------

-- http://www.postgresql.org/docs/current/static/monitoring-stats.html

pgstatServer	OBJECT IDENTIFIER ::= { pgStatMIB 1 }

pgstatServerDatabaseCount OBJECT-TYPE
	SYNTAX		Integer32
	MAX-ACCESS	read-only
	STATUS		current
	DESCRIPTION
		"Number of databases in the server instance."
	::= { pgstatServer 1 }

pgstatServerSize OBJECT-TYPE
    SYNTAX     Unsigned32
    MAX-ACCESS read-only
    STATUS     current
    DESCRIPTION
        "Sum of all database sizes (in bytes)."
    ::= { pgstatServer 2 }

pgstatServerBackends OBJECT-TYPE
    SYNTAX     Gauge32
    MAX-ACCESS read-only
    STATUS     current
    DESCRIPTION
        "Total number of backends (i.e., connections) in the server."
    ::= { pgstatServer 3 }

pgstatServerCommits OBJECT-TYPE
    SYNTAX     Counter32
    MAX-ACCESS read-only
    STATUS     current
    DESCRIPTION
        "Total number of commits in the server."
    ::= { pgstatServer 4 }

pgstatServerRollbacks OBJECT-TYPE
    SYNTAX     Counter32
    MAX-ACCESS read-only
    STATUS     current
    DESCRIPTION
        "Total number of rollbacks in the server."
    ::= { pgstatServer 5 }

pgstatServerBlocksRead OBJECT-TYPE
    SYNTAX     Counter32
    MAX-ACCESS read-only
    STATUS     current
    DESCRIPTION
        "Total number of blocks read in the server (i.e., physical access was made)."
    ::= { pgstatServer 6 }

pgstatServerBlocksHit OBJECT-TYPE
    SYNTAX     Counter32
    MAX-ACCESS read-only
    STATUS     current
    DESCRIPTION
        "Total number of blocks hit in the server (i.e., data retrieved from memory)."
    ::= { pgstatServer 7 }

pgstatServerRollbackRatio OBJECT-TYPE
    SYNTAX     Unsigned32 (0..10000)
    MAX-ACCESS read-only
    STATUS     current
    DESCRIPTION
        "Rollback ratio in the entire server (the lower the better)."
    ::= { pgstatServer 8 }

pgstatServerCacheHitRatio OBJECT-TYPE
    SYNTAX     Unsigned32 (0..10000)
    MAX-ACCESS read-only
    STATUS     current
    DESCRIPTION
        "Cache hit ratio in the entire server (the higher the better)."
    ::= { pgstatServer 9 }

----------------------------------------------------------------

-- http://www.postgresql.org/docs/current/static/monitoring-stats.html#PG-STAT-DATABASE-VIEW
-- http://www.postgresql.org/docs/current/static/functions-admin.html

pgstatDatabaseTable OBJECT-TYPE
    SYNTAX     SEQUENCE OF PgStatDatabaseEntry
    MAX-ACCESS not-accessible
    STATUS     current
    DESCRIPTION
        "Contains one row for each database in the instance, showing database-wide statistics (pg_stat_database)."
    ::= { pgStatMIB 2 }

pgstatDatabaseEntry OBJECT-TYPE
    SYNTAX     PgStatDatabaseEntry
    MAX-ACCESS not-accessible
    STATUS     current
    DESCRIPTION
        "An entry for one database contained by the instance."
    INDEX { pgstatDatabaseId }
    ::= { pgstatDatabaseTable 1 }

PgStatDatabaseEntry ::= SEQUENCE {
	pgstatDatabaseId				Integer32,
	pgstatDatabaseName				DisplayString,
    pgstatDatabaseSize				Unsigned32,
	pgstatDatabaseBackends			Gauge32,
	pgstatDatabaseCommits			Counter32,
	pgstatDatabaseRollbacks			Counter32,
	pgstatDatabaseBlocksRead		Counter32,
	pgstatDatabaseBlocksHit			Counter32,
	pgstatDatabaseTuplesReturned	Counter32,
	pgstatDatabaseTuplesFetched		Counter32,
	pgstatDatabaseTuplesInserted	Counter32,
	pgstatDatabaseTuplesUpdated		Counter32,
	pgstatDatabaseTuplesDeleted		Counter32,
	pgstatDatabaseRollbackRatio		Integer32,
	pgstatDatabaseCacheHitRatio		Integer32,
	pgstatDatabaseTuplesModified	Counter32
}

pgstatDatabaseId OBJECT-TYPE
    SYNTAX     Integer32 (1..2147483647)
    MAX-ACCESS read-only
    STATUS     current
    DESCRIPTION
        "A unique value for each database contained by the instance. Internally it represents the OID of a database in PostgreSQL (datid). Therefore, this value remains constant for each database regardless the agent is restarted."
    ::= { pgstatDatabaseEntry 1 }

pgstatDatabaseName OBJECT-TYPE
    SYNTAX     DisplayString (SIZE (0..64))
    MAX-ACCESS read-only
    STATUS     current
    DESCRIPTION
        "Name of this database (datname)."
    ::= { pgstatDatabaseEntry 2 }

pgstatDatabaseSize OBJECT-TYPE
    SYNTAX     Unsigned32
    MAX-ACCESS read-only
    STATUS     current
    DESCRIPTION
        "Disk space used by the database (in bytes)."
    ::= { pgstatDatabaseEntry 3 }

pgstatDatabaseBackends OBJECT-TYPE
    SYNTAX     Gauge32
    MAX-ACCESS read-only
    STATUS     current
    DESCRIPTION
        "Number of backends currently connected to this database (numbackends). This is the only column in this view that returns a value reflecting current state; all other columns return the accumulated values since the last reset."
    ::= { pgstatDatabaseEntry 4 }

pgstatDatabaseCommits OBJECT-TYPE
    SYNTAX     Counter32
    MAX-ACCESS read-only
    STATUS     current
    DESCRIPTION
        "Number of transactions in this database that have been committed (xact_commit)."
    ::= { pgstatDatabaseEntry 5 }

pgstatDatabaseRollbacks OBJECT-TYPE
    SYNTAX     Counter32
    MAX-ACCESS read-only
    STATUS     current
    DESCRIPTION
        "Number of transactions in this database that have been rolled back (xact_rollback)."
    ::= { pgstatDatabaseEntry 6 }

pgstatDatabaseBlocksRead OBJECT-TYPE
    SYNTAX     Counter32
    MAX-ACCESS read-only
    STATUS     current
    DESCRIPTION
        "Number of disk blocks read in this database (blks_read)."
    ::= { pgstatDatabaseEntry 7 }

pgstatDatabaseBlocksHit OBJECT-TYPE
    SYNTAX     Counter32
    MAX-ACCESS read-only
    STATUS     current
    DESCRIPTION
        "Number of times disk blocks were found already in the buffer cache, so that a read was not necessary (blks_hit). This only includes hits in the PostgreSQL buffer cache, not the operating system's file system cache."
    ::= { pgstatDatabaseEntry 8 }

pgstatDatabaseTuplesReturned OBJECT-TYPE
    SYNTAX     Counter32
    MAX-ACCESS read-only
    STATUS     current
    DESCRIPTION
        "Number of rows returned by queries in this database (tup_returned)."
    ::= { pgstatDatabaseEntry 9 }

pgstatDatabaseTuplesFetched OBJECT-TYPE
    SYNTAX     Counter32
    MAX-ACCESS read-only
    STATUS     current
    DESCRIPTION
        "Number of rows fetched by queries in this database (tup_fetched)."
    ::= { pgstatDatabaseEntry 10 }

pgstatDatabaseTuplesInserted OBJECT-TYPE
    SYNTAX     Counter32
    MAX-ACCESS read-only
    STATUS     current
    DESCRIPTION
        "Number of rows inserted by queries in this database (tup_inserted)."
    ::= { pgstatDatabaseEntry 11 }

pgstatDatabaseTuplesUpdated OBJECT-TYPE
    SYNTAX     Counter32
    MAX-ACCESS read-only
    STATUS     current
    DESCRIPTION
        "Number of rows updated by queries in this database (tup_updated)."
    ::= { pgstatDatabaseEntry 12 }

pgstatDatabaseTuplesDeleted OBJECT-TYPE
    SYNTAX     Counter32
    MAX-ACCESS read-only
    STATUS     current
    DESCRIPTION
        "Number of rows deleted by queries in this database (tup_deleted)."
    ::= { pgstatDatabaseEntry 13 }

pgstatDatabaseRollbackRatio OBJECT-TYPE
    SYNTAX     Unsigned32 (0..10000)
    MAX-ACCESS read-only
    STATUS     current
    DESCRIPTION
        "The ratio in which rollbacks are raised over all operations made in the database."
    ::= { pgstatDatabaseEntry 14 }

pgstatDatabaseCacheHitRatio OBJECT-TYPE
    SYNTAX     Unsigned32 (0..10000)
    MAX-ACCESS read-only
    STATUS     current
    DESCRIPTION
        "The ratio in which data is already cached (i.e., found in memory) over all blocks reads made in the database."
    ::= { pgstatDatabaseEntry 15 }

pgstatDatabaseTuplesModified OBJECT-TYPE
    SYNTAX     Counter32
    MAX-ACCESS read-only
    STATUS     current
    DESCRIPTION
        "Number of rows inserted, updated and deleted by queries in this database."
    ::= { pgstatDatabaseEntry 16 }

----------------------------------------------------------------

-- http://www.postgresql.org/docs/current/static/monitoring-stats.html#PG-STAT-BGWRITER-VIEW

pgstatBgWriter	OBJECT IDENTIFIER ::= { pgStatMIB 20 }

pgstatBgWriterCheckpointsTimed OBJECT-TYPE
	SYNTAX		Counter32
	MAX-ACCESS	read-only
	STATUS		current
	DESCRIPTION
		"Number of scheduled checkpoints that have been performed (checkpoints_timed)."
	::= { pgstatBgWriter 1 }

pgstatBgWriterCheckpointsRequested OBJECT-TYPE
	SYNTAX		Counter32
	MAX-ACCESS	read-only
	STATUS		current
	DESCRIPTION
		"Number of requested checkpoints that have been performed (checkpoints_req)."
	::= { pgstatBgWriter 2 }

pgstatBgWriterBuffersCheckpoint OBJECT-TYPE
	SYNTAX		Counter32
	MAX-ACCESS	read-only
	STATUS		current
	DESCRIPTION
		"Number of buffers written during checkpoints (buffers_checkpoint)."
	::= { pgstatBgWriter 3 }

pgstatBgWriterBuffersClean OBJECT-TYPE
	SYNTAX		Counter32
	MAX-ACCESS	read-only
	STATUS		current
	DESCRIPTION
		"Number of buffers written by the background writer (buffers_clean)."
	::= { pgstatBgWriter 4 }

pgstatBgWriterMaxWrittenClean OBJECT-TYPE
	SYNTAX		Counter32
	MAX-ACCESS	read-only
	STATUS		current
	DESCRIPTION
		"Number of times the background writer stopped a cleaning scan because it had written too many buffers (maxwritten_clean)."
	::= { pgstatBgWriter 5 }

pgstatBgWriterBuffersBackend OBJECT-TYPE
	SYNTAX		Counter32
	MAX-ACCESS	read-only
	STATUS		current
	DESCRIPTION
		"Number of buffers written directly by a backend (buffers_backend)."
	::= { pgstatBgWriter 6 }

pgstatBgWriterBuffersAllocated OBJECT-TYPE
	SYNTAX		Counter32
	MAX-ACCESS	read-only
	STATUS		current
	DESCRIPTION
		"Number of buffers allocated (buffers_alloc)."
	::= { pgstatBgWriter 7 }

---------------------------------------

END
